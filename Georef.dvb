Attribute VB_Name = "FileDialogs"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
Option Explicit

'Notice: Don't forget to set the OwnerHwnd property to the
'handle of the calling window in order to bind the dialog
'to the calling window.

'//The Win32 API Functions///
Private Declare PtrSafe Function GetSaveFileName Lib _
"comdlg32.dll" Alias "GetSaveFileNameA" _
(pOpenfilename As OPENFILENAME) As Long

Private Declare PtrSafe Function GetOpenFileName Lib "comdlg32.dll" Alias _
            "GetOpenFileNameA" (pOpenfilename As OPENFILENAME) As Long


'//Available Flags///
Private Const OFN_ALLOWMULTISELECT = &H200
Private Const OFN_CREATEPROMPT = &H2000
Private Const OFN_ENABLEHOOK = &H20
Private Const OFN_ENABLETEMPLATE = &H40
Private Const OFN_ENABLETEMPLATEHANDLE = &H80
Private Const OFN_EXPLORER = &H80000                         '  new look commdlg
Private Const OFN_EXTENSIONDIFFERENT = &H400
Private Const OFN_FILEMUSTEXIST = &H1000
Private Const OFN_HIDEREADONLY = &H4
Private Const OFN_LONGNAMES = &H200000                       '  force long names for 3.x modules
Private Const OFN_NOCHANGEDIR = &H8
Private Const OFN_NODEREFERENCELINKS = &H100000
Private Const OFN_NOLONGNAMES = &H40000                      '  force no long names for 4.x modules
Private Const OFN_NONETWORKBUTTON = &H20000
Private Const OFN_NOREADONLYRETURN = &H8000
Private Const OFN_NOTESTFILECREATE = &H10000
Private Const OFN_NOVALIDATE = &H100
Private Const OFN_OVERWRITEPROMPT = &H2
Private Const OFN_PATHMUSTEXIST = &H800
Private Const OFN_READONLY = &H1
Private Const OFN_SHAREAWARE = &H4000
Private Const OFN_SHAREFALLTHROUGH = 2
Private Const OFN_SHARENOWARN = 1
Private Const OFN_SHAREWARN = 0
Private Const OFN_SHOWHELP = &H10


'//The Structure
Private Type OPENFILENAME
        lStructSize As Long
        hwndOwner As LongPtr
        hInstance As LongPtr
        lpstrFilter As String
        lpstrCustomFilter As String
        nMaxCustFilter As Long
        nFilterIndex As Long
        lpstrFile As String
        nMaxFile As Long
        lpstrFileTitle As String
        nMaxFileTitle As Long
        lpstrInitialDir As String
        lpstrTitle As String
        flags As Long
        nFileOffset As Integer
        nFileExtension As Integer
        lpstrDefExt As String
        lCustData As LongPtr
        lpfnHook As LongPtr
        lpTemplateName As String
End Type

'private class variables
Private lngHwnd As Long
Private strFilter As String
Private strTitle As String
Private strDir As String
Private strFile As String   'elj
Private lngSelectedFilter As Long
Private blnHideReadOnly As Boolean
Private blnMode As Boolean

Private Sub Class_Initialize()
  'Set default values when
  'class is first created
  strDir = CurDir
  strTitle = "Llamas Rule"
  strFile = ""
  strFilter = "All Files" _
  & Chr$(0) & "*.*" & Chr$(0)
  lngSelectedFilter = 0
  lngHwnd = &O0 'Desktop
End Sub

Public Property Let ownerHwnd(WindowHandle As Long)
  '//FOR YOU TODO//
  'Use the API to validate this handle
  lngHwnd = WindowHandle
  'R14 users who just want to use this code:
  'Simple, don't set this property! the default
  'of &0 will work fine for most of your needs
End Property

Public Property Get ownerHwnd() As Long
  ownerHwnd = lngHwnd
End Property

'elj added property
Public Property Let MultiSelect(mode As Boolean)
    blnMode = mode
End Property

'elj added property
Public Property Get MultiSelect() As Boolean
  MultiSelect = blnMode
End Property

Public Property Get SelectedFilter() As Long
  SelectedFilter = lngSelectedFilter
End Property

Public Property Let SelectedFilter(FilterNumber As Long)
  lngSelectedFilter = FilterNumber
End Property

'elj added property
Public Property Let StartFile(FileName As String)
  'don't allow null strings
  If Not FileName = vbNullString Then
    strFile = FileName
  End If
End Property

'elj added property
Public Property Get StartFile() As String
  StartFile = strFile
End Property

Public Property Let StartInDir(StartDir As String)
  'don't allow null strings
  If Not StartDir = vbNullString Then
    strDir = StartDir
  End If
End Property

Public Property Get StartInDir() As String
  StartInDir = strDir
End Property


Public Property Let Title(Caption As String)
  'don't allow null strings
  If Not Caption = vbNullString Then
    strTitle = Caption
  End If
End Property

Public Property Get Title() As String
  Title = strTitle
End Property

Public Property Let Filter(ByVal FilterString As String)
  'Filters change the type of files that are
  'displayed in the dialog. I have designed this
  'validation to use the same filter format the
  'Common dialog OCX uses:
  '"All Files (*.*)|*.*"
  Dim intPos As Integer
  Do While InStr(FilterString, "|") > 0
    intPos = InStr(FilterString, "|")
    If intPos > 0 Then
      FilterString = Left$(FilterString, intPos - 1) _
      & Chr$(0) & Right$(FilterString, _
      Len(FilterString) - intPos)
    End If
  Loop
  If Right$(FilterString, 2) <> Chr$(0) & Chr$(0) Then
    FilterString = FilterString & Chr$(0)
  End If
  strFilter = FilterString
End Property


Public Property Get Filter() As String
  'Here we reverse the process and return
  'the Filter in the same format that it was
  'entered
  Dim intPos As Integer
  Dim strTemp As String
  strTemp = strFilter
  Do While InStr(strTemp, Chr$(0)) > 0
    intPos = InStr(strTemp, Chr$(0))
    If intPos > 0 Then
      strTemp = Left$(strTemp, intPos - 1) _
      & "|" & Right$(strTemp, _
      Len(strTemp) - intPos)
    End If
  Loop
  If Right$(strTemp, 1) = "|" Then
    strTemp = Left$(strTemp, Len(strTemp) - 1)
  End If
  Filter = strTemp
End Property

Public Property Let HideReadOnly(blnVal As Boolean)
  'Simple one
  blnHideReadOnly = blnVal
End Property

Public Property Get HideReadOnly() As Boolean
  HideReadOnly = blnHideReadOnly
End Property

'@~~~~~~~~~~~~~~~~~~~~~~~~~~~~~~~~~~~~~~~~~~~~~~~~@
' Display and use the File open dialog
'@~~~~~~~~~~~~~~~~~~~~~~~~~~~~~~~~~~~~~~~~~~~~~~~~@
Public Function ShowOpen() As String
  Dim strTemp As String
  Dim udtStruct As OPENFILENAME
  Dim lReturn     As Long

  'Use our private variable
  udtStruct.hwndOwner = lngHwnd
  'Use our private variable
  udtStruct.lpstrFilter = strFilter
  udtStruct.nFilterIndex = lngSelectedFilter
  'elj start
  udtStruct.lpstrFile = String(257, " ")

  'elj end
  #If VBA7 Then
    udtStruct.nMaxFile = LenB(udtStruct.lpstrFile) - 1
    udtStruct.lStructSize = LenB(udtStruct)
  #Else
    udtStruct.nMaxFile = Len(udtStruct.lpstrFile) - 1
    udtStruct.lStructSize = Len(udtStruct)
  #End If
  udtStruct.lpstrFileTitle = Space$(254)
  udtStruct.nMaxFileTitle = 255
  'Use our private variable
  udtStruct.lpstrInitialDir = strDir
  'Use our private variable
  udtStruct.lpstrTitle = strTitle
  'Ok, here we test our boolean to
  'set the flags
  udtStruct.flags = 0
  If blnHideReadOnly Then udtStruct.flags = OFN_HIDEREADONLY + udtStruct.flags
  If blnMode Then udtStruct.flags = OFN_ALLOWMULTISELECT + udtStruct.flags
  udtStruct.flags = OFN_EXPLORER + udtStruct.flags
  lReturn = GetOpenFileName(udtStruct)
  If lReturn = 1 Then
    strTemp = (Trim(udtStruct.lpstrFile))
    ShowOpen = Mid(strTemp, 1, Len(strTemp) - 1)
  End If
End Function

'@~~~~~~~~~~~~~~~~~~~~~~~~~~~~~~~~~~~~~~~~~~~~~~~~@
' Display and use the File Save dialog
'@~~~~~~~~~~~~~~~~~~~~~~~~~~~~~~~~~~~~~~~~~~~~~~~~@
Public Function ShowSave() As String
    Dim strTemp As String
  Dim udtStruct As OPENFILENAME
  udtStruct.lStructSize = Len(udtStruct)
  'Use our private variable
  udtStruct.hwndOwner = lngHwnd
  'Use our private variable
  udtStruct.lpstrFilter = strFilter
'  udtStruct.lpstrFile = Space$(254)    'elj comment out
  'elj start
  If Not strFile = vbNullString Then
    udtStruct.lpstrFile = strFile & Space(2000 - Len(strFile))
  Else
    udtStruct.lpstrFile = Space$(2000)
  End If
  'elj end
  udtStruct.nMaxFile = 254
  udtStruct.lpstrFileTitle = Space$(254)
  udtStruct.nMaxFileTitle = 255
  'Use our private variable
  udtStruct.lpstrInitialDir = strDir
  'Use our private variable
  udtStruct.lpstrTitle = strTitle
  'Ok, here we test our flag
  If blnHideReadOnly Then
    udtStruct.flags = OFN_HIDEREADONLY
  Else
    udtStruct.flags = 0
  End If
  If GetSaveFileName(udtStruct) Then
    strTemp = (Trim(udtStruct.lpstrFile))
    ShowSave = Mid(strTemp, 1, Len(strTemp) - 1)
  End If
End Function

Attribute VB_Name = "Georef_Automation"
' -------------- '
' --- HEADER --- '
' -------------- '

'''
' AutoCAD automated georeferencing
'
' Author: Mike Halbheer
' Status: Stable
' Version: 1.0.3
'''

Option Explicit


' ------------------------ '
' --- TYPE DEFINITIONS --- '
' ------------------------ '

Public Type Point_Data
    '''
    ' Data type to include the information about the selected points
    '
    ' Properties
    ' ----------
    ' Points_Input : Variant
    '   The points selected in the input data
    ' Points_Reference : Variant
    '   The points selected in the reference data
    ' numPoints : Integer
    '   The number of point similarities
    '''
    
    Points_Input As Variant
    Points_Reference As Variant
    numPoints As Integer
End Type

Public Type trafo_Params
    '''
    ' Data type to capture the transformation parameters of the Helmert transformation
    '
    ' Properties
    ' ----------
    ' Translation : Array of Doubles
    '   The 3D shift to be applied to the data. (y,x,z) Geodetic, (x,y,z) AutoCAD
    ' Rotation : Double
    '   The rotation around the z Axis
    ' HelmertScale : Double
    '   The factor the data should be scaled with
    ' ZeroShift : Array of Doubles
    '   The 3D shift of the origin to the center of gravity of the selected points. (y,x,z) Geodetic, (x,y,z) AutoCAD
    '''
    
    Translation(0 To 2) As Double
    Rotation As Double
    HelmertScale As Double
    ZeroShift(0 To 2) As Double
End Type

Private Declare PtrSafe Function FindWindow Lib "user32.dll" Alias "FindWindowA" (ByVal lpClassName As Any, ByVal lpWindowName As Any) As Long

' ------------------- '
' --- SUBROUTINES --- '
' ------------------- '

Sub Main()
    
    frm_0_New_Old.show
    
    If frm_0_New_Old.Tag = "0" Then
        ' Show form to find the reference data and data to be referenced
        frm_1_Georef.show vbModeless
    Else
        Apply_To_New_Plans
    End If
End Sub

Sub Execute_Georef(path_input As String, path_reference As String)
    '''
    ' Starts the actual georeferencing process by loading the two plans
    '
    ' Parameters
    ' ----------
    ' path_input : String
    '   The path to the input plan
    ' path_reference : String
    '   The path to the reference plan
    '''
    
    Dim path_output As String ' The path of the resulting DWG
    
    Dim boundingBox_input As Variant ' The bounding box of the input plan
    Dim boundingBox_reference As Variant ' The boudning box of the reference plan
    
    
    
    ' Create new drawing
    path_output = Left(path_input, (Len(path_input) - 4)) & "_georef.dwg"
    On Error GoTo Handler:
        CreateAutoCADFile (path_output)
    GoTo success
        
    ' Handle exception if document is open
Handler:
    MsgBox "Dokument ist geöffnet und muss zuerst geschlossen werden", vbOKOnly, "Dokument geöffnet"
    End
    
success:
    ' Reference drawings, create two viewports and zoom to content
    boundingBox_input = Add_Block_From_File(path_input)
    boundingBox_reference = Add_Block_From_File(path_reference)
    
    Split_View boundingBox_input, boundingBox_reference
    
End Sub

Sub Match_Plans(path_input As String)
    '''
    ' Matches the two plans by having the user pick point similarities and the logging them for further processing in Python
    '
    ' Parameters
    ' ----------
    ' path_input : String
    '   The path of the input plan. Used to save the logfile in the same directory
    '''

    Dim path_logfile As String ' Path to the logfile
    Dim path_sim_coords As String ' Path to the file containing the similarity coordinates
    Dim exepath As String ' Path to the executable of the Python script
    Dim path_trafo As String ' Path where the transformation parameters are stored
    
    Dim FSO As Object ' File System Object, helper to create TXT
    Dim Log_file As Object ' The logfile object
    
    Dim Similarity_Coords As Object ' The Similarity Points TXT object
    
    Dim known_scale As Double ' The scale, if defined. Otherwise -1
    
    Dim ShellCommand As String ' The command to be sent to the shell
    
    Dim trafoParams As trafo_Params ' The trafo_Params object containing the Helmert transformation parameters
    
    Dim Point_Info As Point_Data ' The information about the selected points
    
    Dim i As Integer ' Helper variable for iteration
    Dim acceptedScale As Boolean ' Helper variable to allow the user to accept the scale
    Dim msg_val As Integer ' The value of the MsgBox propmpts
    
    Dim additionalFiles As Variant ' Contains the paths of the additional files
    Dim allConverted As Boolean ' Checks wheter all plans were converted
    
    ' Define the constants
    exepath = "H:\Software\AutoCAD\Scripts\Georeferenzierung\estimate_helmert.exe"
    path_logfile = Left(path_input, (Len(path_input) - 4)) & "_log.txt"
    path_sim_coords = Left(path_input, (Len(path_input) - 4)) & "_coords.txt"
    path_trafo = Left(path_input, (Len(path_input) - 4)) & "_trafo.txt"
    
    ' Define the iteration condition
    acceptedScale = False
    
    ' Have the user pick the point similarities
    Point_Info = Pick_Point_Similarities()
    
    
    While Not acceptedScale
        ' Create a txt file for the logfile and the similaritiy coords CSV
        Set FSO = CreateObject("Scripting.FileSystemObject")
        Set Log_file = FSO.CreateTextFile(path_logfile)
        Set Similarity_Coords = FSO.CreateTextFile(path_sim_coords)
        
        ' Logfile Header
        Log_file.WriteLine "GEOREFERENZIERUNG - PROTOKOLL"
        Log_file.WriteLine "============================="
        Log_file.WriteLine ""
        ' Similarity coordinates
        Log_file.WriteLine "Passpunkte"
        Log_file.WriteLine "=========="
        Log_file.WriteLine "Passpunkte Fremddaten"
        Log_file.WriteLine "---------------------"
        Log_file.WriteLine "Punktnummer Y   X"
        
        ' Write the coordinates into the respective files
        For i = 0 To Point_Info.numPoints - 1
            Log_file.WriteLine i & "    " & Point_Info.Points_Input(2 * i) & "  " & Point_Info.Points_Input(2 * i + 1)
            Similarity_Coords.WriteLine i & "," & Point_Info.Points_Input(2 * i) & "," & Point_Info.Points_Input(2 * i + 1) & ",0"
        Next i
        
        Log_file.WriteLine ""
        Log_file.WriteLine "Passpunkte Refernzdaten"
        Log_file.WriteLine "-----------------------"
        Log_file.WriteLine "Punktnummer Y   X"
        
        ' Write the coordinates into the respective files
        For i = 0 To Point_Info.numPoints - 1
            Log_file.WriteLine i & "    " & Point_Info.Points_Reference(2 * i) & "  " & Point_Info.Points_Reference(2 * i + 1)
            Similarity_Coords.WriteLine i & "," & Point_Info.Points_Reference(2 * i) & "," & Point_Info.Points_Reference(2 * i + 1) & ",1"
        Next i
        
        ' Close the logfile object
        Log_file.Close
        
        ' Prompt the user for the input of a known scale if any
        frm_4_Scale.show
        
        known_scale = frm_4_Scale.known_scale

        ' Append the scale. NaN if no known scale is given, else the scale
        If known_scale = -1 Then
            Similarity_Coords.WriteLine "NaN,NaN,NaN,2"
        Else
            Similarity_Coords.WriteLine "NaN," & known_scale & ",NaN,2"
        End If
        
        ' Close the similarity coordinates object
        Similarity_Coords.Close
    
        ' Construct the command to be sent to the command shell
        ShellCommand = """" & exepath & """" & " " & """" & path_sim_coords & """"
        
        ' Start a shell process to launch the pyhton file and wait for its completion
        ShellProcess.ExecCmd CStr(ShellCommand)
        
        ' Read the transformation parameters
        trafoParams = Read_Trafo_CSV(path_trafo)
        
        ' If no known scale was set ask the user wheter they want to change the estimated scale
        If known_scale = -1 Then
            msg_val = MsgBox("Der geschätzte Massstab ist " & trafoParams.HelmertScale & ". Soll er auf einen festen Massstab gerundet werden?", vbYesNo, "Massstab runden")
            If msg_val = 7 Then
                ' User is fine with the scale
                acceptedScale = True
            End If
        Else
            ' A user defined scale was set
            acceptedScale = True
        End If
    Wend
    
    ' Move the input plan
    Call Move_Input(path_input, trafoParams)
        
    ' Clean up the working directory
    Delete_File path_sim_coords
    ' Delete_File path_trafo
    
    ' Allow for processing of additional plans
    allConverted = False
    
    While Not allConverted
        msg_val = MsgBox("Soll die Transformation auf weitere Pläne angewandt werden?" & vbCrLf & "Notiz: Bei langen Pfadnamen müssen die Pläne in den Transfer und anschliessend zurückkopiert werden (Pfadlängenbeschränkung).", vbYesNo, "Weitere Pläne transformieren?")
        If msg_val = 6 Then
            additionalFiles = Load_Additional_Files(path_input)
            
            Georef_Additional_Plans additionalFiles, trafoParams
        Else
            allConverted = True
        End If
    Wend

End Sub

Sub Move_Input(path_input As String, trafoParams As trafo_Params)
    '''
    ' Moves the input plan according to the transformation parameters
    '
    ' Parameters
    ' ----------
    ' path_input : String
    '   The path of the input plan. Used to reconstruct the Block Name
    ' trafoParams : trafo_Params
    '   The transformation parameters as were loaded
    '''
    
    Dim lockedLayers() As Boolean ' Array to store lockign state
    Dim Layers As AcadLayers ' Helper variable
    Dim numLayers As Integer ' The number of layers in the project
    Dim Layer As AcadLayer ' Iterator variable
    
    Dim BlockName As String ' The name of the inserted block reference
    
    Dim FSO As Object ' Helper file system object
    
    Dim zeroPoint(0 To 2) As Double ' The origin of the coordinate system
    Dim BlockRef As Object ' Iterator variable
    Dim ent As AcadEntity ' Iterator variable
    
    Dim i As Integer ' Iterator variable
    
    ' Count number of layers in the project
    numLayers = 0
    For Each Layer In ThisDrawing.Layers
        numLayers = numLayers + 1
    Next Layer
    
    ' Initialize size
    ReDim lockedLayers(numLayers)

    ' Unlock all layers and store state to revert later
    i = 0
    For Each Layer In ThisDrawing.Layers
        If Layer.Lock = True Then
            Layer.Lock = False
            lockedLayers(i) = True
        Else
            lockedLayers(i) = False
        End If
        i = i + 1
    Next Layer
    
    ' Define Helper FSO
    Set FSO = CreateObject("Scripting.FileSystemObject")
    BlockName = FSO.GetBaseName(path_input) ' Get the name of the block reference
    
    ' Define the origin as a helper
    zeroPoint(0) = 0: zeroPoint(1) = 0: zeroPoint(2) = 0
        
    ' Transform both the input plan and the helper polyline
    For Each ent In ThisDrawing.ModelSpace
        ' Find block reference with proper name
        If ent.ObjectName = "AcDbBlockReference" Then
            Set BlockRef = ent
            If BlockRef.Name = BlockName Then
                BlockRef.Rotate trafoParams.ZeroShift, trafoParams.Rotation
                BlockRef.Move zeroPoint, trafoParams.Translation
                BlockRef.ScaleEntity zeroPoint, trafoParams.HelmertScale

            End If
        ' Find polyline on layer created earlier
        ElseIf ent.ObjectName = "AcDbPolyline" Then
            Set BlockRef = ent
            If BlockRef.Layer = "Fremddaten Georeferenzierung" Then
                BlockRef.Rotate trafoParams.ZeroShift, trafoParams.Rotation
                BlockRef.Move zeroPoint, trafoParams.Translation
                BlockRef.ScaleEntity zeroPoint, trafoParams.HelmertScale
            End If
        End If
    Next ent

    ' Revert layer locking state
    i = 0
    For Each Layer In ThisDrawing.Layers
        Layer.Lock = lockedLayers(i)
        i = i + 1
    Next Layer
    
    ' Save the drawing
    ThisDrawing.Save
End Sub

Sub Georef_Additional_Plans(ByVal file_paths As Variant, trafoParams As trafo_Params)
    
    Dim file_path As String
    Dim path_output As String
    Dim boundingBox As Variant
    
    Dim i As Integer
    Dim numFiles As Integer
    
    Dim input_path As String
    
    numFiles = UBound(file_paths)
    
    For i = 0 To numFiles
    
        input_path = file_paths(i)
    
        ' Create new drawing
        path_output = Left(input_path, (Len(input_path) - 4)) & "_georef.dwg"
        
        On Error GoTo Handler:
            CreateAutoCADFile (path_output)
        GoTo success
            
        ' Handle exception if document is open
Handler:
Debug.Print (Err.Description)
        MsgBox "Dokument ist geöffnet und muss zuerst geschlossen werden", vbOKOnly, "Dokument geöffnet"
        End
            
success:
        
        boundingBox = Add_Block_From_File(input_path)
        
        Move_Input input_path, trafoParams
    
        ThisDrawing.Application.ActiveDocument.Close (True)
        
        
    Next i
       
End Sub

Sub Delete_File(Filepath As String)
    '''
    ' Function to delete the temporary helper files used
    '
    ' Parameters
    ' ----------
    ' filePath : String
    '   The path of the file to be deleted
    '''

    If (Dir(Filepath) <> "") Then
        ' Remove readOnly tag if it were to exist
        SetAttr Filepath, vbNormal
        
        ' Remove the file
        Kill Filepath
    End If
End Sub

Sub Split_View(bbox_input As Variant, bbox_reference As Variant)

    '''
    ' Functiong to create a split view, showing the input file and the reference file
    '
    ' Parameters
    ' ----------
    ' bbox_input : TypedArray
    '   The bounding box of the input file
    ' bbox_reference : TypedArray
    '   The bounding box of the reference file
    '''
    
    Dim viewport_Input As AcadViewport ' Viewport for the input plan
    Dim viewport_Reference As AcadViewport ' Viewport for the reference plan
    
    Dim point1(0 To 2) As Double ' Helper point
    Dim point2(0 To 2) As Double ' Helper point
    
    Dim center1_2D(0 To 1) As Double ' Center of first viewport
    Dim center2_2D(0 To 1) As Double ' Center of second viewport
    
    ' Switch to model space
    ThisDrawing.ActiveSpace = acModelSpace
    
    ' Create the two viewports
    Set viewport_Input = ThisDrawing.ActiveViewport
    
    ' Define the extent the viewport needs to be zoomed to
    point1(0) = bbox_input(0): point1(1) = bbox_input(1): point1(2) = 0
    point2(0) = bbox_input(3): point2(1) = bbox_input(4): point2(2) = 0
    center1_2D(0) = ((bbox_input(0) + bbox_input(3)) / 2): center1_2D(1) = ((bbox_input(1) + bbox_input(4)) / 2)
    
    ' Center the viewport and zoom to fit
    viewport_Input.Center = center1_2D
    viewport_Input.Width = Abs(bbox_input(0) - bbox_input(3))
    viewport_Input.Height = Abs(bbox_input(1) - bbox_input(4))
    
    ThisDrawing.ActiveViewport = viewport_Input
    ZoomWindow point1, point2
    
    ' Define the extent the viewport needs to be zoomed to
    viewport_Input.Split acViewport2Vertical
    point1(0) = bbox_reference(0): point1(1) = bbox_reference(1): point1(2) = 0
    point2(0) = bbox_reference(3): point2(1) = bbox_reference(4): point2(2) = 0
    center2_2D(0) = ((bbox_reference(0) + bbox_reference(3)) / 2): center2_2D(1) = ((bbox_reference(1) + bbox_reference(4)) / 2)
    
    ' Center the viewport and zoom to fit
    viewport_Input.Center = center2_2D
    viewport_Input.Width = Abs(bbox_reference(0) - bbox_reference(3))
    viewport_Input.Height = Abs(bbox_reference(1) - bbox_reference(4))
    
    ThisDrawing.ActiveViewport = viewport_Input
    ZoomWindow point1, point2

End Sub


' ----------------- '
' --- FUNCTIONS --- '
' ----------------- '

Public Function CreateAutoCADFile(file_path As String) As AcadDocument
    '''
    ' Function to create a new AutoCAD file at the given location
    
    ' Parameters
    ' ----------
    ' file_path : String
    '   The path of the file to be created
    '
    ' Returns
    ' -------
    ' acadDoc : AcadDocument
    '   Reference to the newly created Document
    '''

    Dim acadDoc As AcadDocument ' The AutoCAD document to be created
    Dim acadApp As AcadApplication ' The AutoCAD application
    
    ' Define the application
    Set acadApp = ThisDrawing.Application
    
    If Len(file_path) > 0 Then
        ' Add the new drawing, then save it
        Set acadDoc = acadApp.Documents.Add
        acadDoc.SaveAs (file_path)
        Set CreateAutoCADFile = acadDoc
    Else
        ' If the file path is illegal, do nothing
        CreateAutoCADFile = Nothing
    End If
    
End Function

Public Function Add_Block_From_File(ByVal file_path As String) As Variant
    '''
    ' Function to add a block reference from a file
    '
    ' Parameters
    ' ----------
    ' file_path : String
    '   The path of the file to be added
    '
    ' Returns
    ' -------
    ' boundingBox : Variant
    '   The bounding box of the added block reference
    '''
    
    Dim boundingBox As Variant ' Bounding box of the block reference
    Dim utilityObject As Object ' Helper to determine bounding box
    
    Dim InsertPoint(0 To 2) As Double ' Point of insertion
    Dim insertedBlock As AcadBlockReference ' Block reference object
    
    Dim minExt As Variant ' Maximal extension in either direction
    Dim maxExt As Variant ' Minimal extension in either direction
    
    ' Insert with original coordinates
    InsertPoint(0) = 0: InsertPoint(1) = 0: InsertPoint(2) = 0
    
    Set insertedBlock = ThisDrawing.ModelSpace.InsertBlock(InsertPoint, file_path, 1, 1, 1, 0)
    insertedBlock.Update
    
    ' Get the bounding box of the inserted block reference
    insertedBlock.GetBoundingBox minExt, maxExt
    
    ' Add bounding box into the respective array
    Set utilityObject = ThisDrawing.Utility
    utilityObject.CreateTypedArray boundingBox, vbDouble, minExt(0), minExt(1), minExt(2), maxExt(0), maxExt(1), maxExt(2)
    
    ' Return value
    Add_Block_From_File = boundingBox
    
End Function

Public Function Pick_Point_Similarities() As Point_Data
    '''
    ' Function to pick the point similarities in the two datasets
    '
    ' Parameters
    ' ----------
    ' None
    '
    ' Returns
    ' -------
    ' Point_Info : Point_Data
    '   The point data object containing the coordinates
    '''
    
    Dim selection_criteria As Integer ' Determines which plans are used
    ' Values must be one of the following
    ' 0: Select in both plans
    ' 1: Select in input plan only
    ' 2: Select in reference plan only
    
    Dim numPoints As Integer ' Number of similarity points
    Dim Points_Input() As Double ' Point coordinates in input data
    Dim Points_Reference() As Double ' Point coordinates in reference data
    
    Dim input_Polyline As AcadLWPolyline ' Polyline for easier control
    Dim reference_Polyline As AcadLWPolyline ' Polyline for easier control
    
    Dim TmpCoords(0 To 2) As Double ' Helper variable
    Dim TmpPoint As Variant ' Helper variable

    Dim Point_Info As Point_Data ' Object containing infos on similarity coords
    
    Dim referenceLayer As String ' Layer the polyline is drawn on
    Dim inputLayer As String ' Layer the polyline is drawn on
    
    Dim Layers As AcadLayers ' Helper variable
    Dim LayerCount As Integer ' Number of layers
    Dim i As Integer ' Iterator variable
    Dim Object As AcadObject ' Iterator variable
    
    Dim msgVal ' Value of the MsgBox prompt
    
    ' Initialize layer names
    referenceLayer = "Referenzdaten Georeferenzierung"
    inputLayer = "Fremddaten Georeferenzierung"
    
    ' Initialize criteria for both plans
    selection_criteria = 0
    
    ' Ask user to enter number of points
Enter_Num_Sims:
    On Error GoTo Handler
        numPoints = ThisDrawing.Utility.GetString(0, "Anzahl Passpunkte eingeben")
    GoTo No_Error:
    
    ' Allow user to repeat on error
Handler:
    msgVal = MsgBox("Anzahl Passpunkte ungültig. Eingabe wiederholen?", vbRetryCancel, "Passpunktanzahl ungültig")
    
    If msgVal = 2 Then
        End
    Else
        Resume Enter_Num_Sims
    End If
    
No_Error:
    ' Initialize the coordinate arrays
    ReDim Points_Input(numPoints * 2 - 1)
    ReDim Points_Reference(numPoints * 2 - 1)
    
Select_Similarities:
    ' Select in input plan
    On Error GoTo Pick_Error_Input
        If selection_criteria = 0 Or selection_criteria = 1 Then

            ' Delete existing polyline if it exists
            Set Layers = ThisDrawing.Layers
            LayerCount = Layers.Count
            For i = 0 To LayerCount - 1
                If Layers.Item(i).Name = inputLayer Then
                    If ThisDrawing.ActiveLayer.Name = inputLayer Then
                        ThisDrawing.ActiveLayer = Layers.Item("0")
                    End If
                    For Each Object In ThisDrawing.ModelSpace
                      If Object.Layer = inputLayer Then
                          Object.Delete
                      End If
                    Next
                End If
            Next
            
            ' Add the layer to the stack and activate it
            ThisDrawing.Layers.Add (inputLayer)
            ThisDrawing.ActiveLayer = ThisDrawing.Layers(inputLayer)
            
            ' Ask user to select points
            For i = 0 To numPoints - 1
                TmpPoint = ThisDrawing.Utility.GetPoint(, i + 1 & ".Punkt in den Fremddaten auswählen")
                Points_Input(2 * i) = TmpPoint(0): Points_Input(2 * i + 1) = TmpPoint(1)
            Next i
                
            ' Create a lightweight Polyline object in model space
            Set input_Polyline = ThisDrawing.ModelSpace.AddLightWeightPolyline(Points_Input)
        End If

    ' Select in reference plan
    On Error GoTo Pick_Error_Reference
        If selection_criteria = 0 Or selection_criteria = 2 Then
            
            ' Delete existing polyline if it exists
            Set Layers = ThisDrawing.Layers
            LayerCount = Layers.Count
            For i = 0 To LayerCount - 1
                If Layers.Item(i).Name = referenceLayer Then
                    If ThisDrawing.ActiveLayer.Name = referenceLayer Then
                        ThisDrawing.ActiveLayer = Layers.Item("0")
                    End If
                    For Each Object In ThisDrawing.ModelSpace
                      If Object.Layer = referenceLayer Then
                          Object.Delete
                      End If
                    Next
                End If
            Next
              
            ' Add the layer to the stack and activate it
            ThisDrawing.Layers.Add (referenceLayer)
            ThisDrawing.ActiveLayer = ThisDrawing.Layers(referenceLayer)
            
            ' Ask user to select points
            For i = 0 To numPoints - 1
                TmpPoint = ThisDrawing.Utility.GetPoint(, i + 1 & ".Punkt in den Referenzdaten auswählen")
                Points_Reference(2 * i) = TmpPoint(0): Points_Reference(2 * i + 1) = TmpPoint(1)
            Next i
            
            ' Create a lightweight Polyline object in model space
            Set reference_Polyline = ThisDrawing.ModelSpace.AddLightWeightPolyline(Points_Reference)
        End If
       
    GoTo Pick_Success
        
Pick_Error_Input:
    ' On error in input plan selection allow user to choose to repeat
    Load frm_3_Stop_Execution
    frm_3_Stop_Execution.Tag = 0 ' Default tag is 0 so both plans will be done
    frm_3_Stop_Execution.show ' Prompt user for repetition
    selection_criteria = frm_3_Stop_Execution.Tag
    Resume Select_Similarities ' Handle error and resume execution before selection
    
Pick_Error_Reference:
    ' On error in reference plan selection allow user to choose to repeat
    Load frm_3_Stop_Execution
    frm_3_Stop_Execution.Tag = 2 ' Default tag is 2 so only reference plan will be done
    frm_3_Stop_Execution.show ' Prompt user for repetition
    selection_criteria = frm_3_Stop_Execution.Tag
    Resume Select_Similarities ' Handle error and resume execution before selection
    
Pick_Success:

    ' Activate layer 0
    ThisDrawing.ActiveLayer = ThisDrawing.Layers("0")
    
    ' Ask user to accept their selection
    frm_3_1_Accept_Sims.show
    
    ' If it was accpeted assign it to Point_Info
    If frm_3_1_Accept_Sims.Tag = -1 Then
        With Point_Info
            .Points_Input = Points_Input
            .Points_Reference = Points_Reference
            .numPoints = numPoints
        End With
        
        ' Return value
        Pick_Point_Similarities = Point_Info
    Else
        ' Repeat the selection
        selection_criteria = frm_3_1_Accept_Sims.Tag
        GoTo Select_Similarities
    End If

End Function

Public Function Read_Trafo_CSV(path_trafo As String) As trafo_Params
    '''
    ' Reads the CSV containing the transformation parameters
    '
    ' Parameters
    ' ----------
    ' path_trafo : String
    '   The path to the transformation CSV file
    '
    ' Returns
    ' -------
    ' trafoParams : trafo_Params
    '   The trafo_params object containing the helmert transformation parameters
    '''
    
    Dim fnum As Integer ' FreeFile object
    Dim fileString As String ' The string obtained from reading file
    Dim fileLines As Variant ' The inidividual lines of the file
    Dim trafoArray As Variant ' The individual columns of the row
    Dim trafoParams As trafo_Params ' Transformation parameters

    ' Define the file object and read stream into string
    fnum = FreeFile
    Open path_trafo For Input As fnum
    fileString = Input$(LOF(fnum), #fnum)
    Close fnum
    
    ' Split the string into lines
    fileLines = Split(fileString, vbCrLf)
    
    ' Split the first row into the columns (file only has one row)
    trafoArray = Split(fileLines(0), ",")
    
    ' Assign read values to the trafo_Params object
    trafoParams.Translation(0) = trafoArray(0)
    trafoParams.Translation(1) = trafoArray(1)
    trafoParams.Translation(2) = 0
    trafoParams.Rotation = -trafoArray(2)
    trafoParams.HelmertScale = trafoArray(3)
    trafoParams.ZeroShift(0) = trafoArray(4)
    trafoParams.ZeroShift(1) = trafoArray(5)
    trafoParams.ZeroShift(2) = 0
    
    ' Return value
    Read_Trafo_CSV = trafoParams
    
End Function

Public Function Load_Additional_Files(path_input As String) As Variant
    '''
    ' Loads the additional files to be georeferenced
    '
    ' Parameters
    ' ----------
    ' path_input : String
    '   The original input directory
    '
    ' Returns
    ' -------
    ' strFileNames : Array of Strings
    '   Array containing the paths to the respective file names
    '''
    
    Dim fd As FileDialogs ' File Dialog object
    Dim strFilter As String ' Data type filter
    Dim strFileName As String ' String being returned by the file dialog
    Dim tmpFileNames As Variant ' String split into individual files
    Dim strFileNames() As String ' Strings concatenated with path
    Dim numFiles As Integer ' Number of files
    
    Dim i As Integer ' Iterator variable
    
    ' Define new file dialog with the given properties
    Set fd = New FileDialogs
    
    strFilter = "Drawings (*.dwg)|*.dwg" ' Only show DWG
    fd.Filter = strFilter
    fd.Title = "Weitere Dateien auswählen"
    fd.StartInDir = Left(path, InStrRev(path_input, "\")) ' Start in same directory as original plan
    fd.MultiSelect = True ' Allow multiple files to be selected
    
    ' Show the fiel dialog
    strFileName = fd.ShowOpen

    ' Split the resulting string
    tmpFileNames = Split(strFileName, vbNullChar)

    If UBound(tmpFileNames) = -1 Then
        MsgBox "Keine Dateien wurden ausgewählt.", vbOKOnly, "Ungültige Auswahl"
        End
    ElseIf UBound(tmpFileNames) = 1 Then
        ' If only one file was selected, the return is a single string
        ReDim strFileNames(0)
        strFileNames(0) = tmpFileNames(0)
    Else
        ' Concatenate the path with the file names
        numFiles = UBound(tmpFileNames) - 1
        ReDim strFileNames(0 To numFiles - 1)
        For i = 0 To numFiles - 1
            strFileNames(i) = tmpFileNames(0) & "\" & tmpFileNames(i + 1)
        Next i
    End If
    
    ' Return
    Load_Additional_Files = strFileNames
    
End Function

Sub Apply_To_New_Plans()
    '''
    ' Subroutine to georeference new plans with
    ' an exisiting set of transformation parameters
    '
    ' Parameters
    ' ----------
    ' None
    '''
    
    Dim fd As FileDialogs ' File Dialog object
    Dim strFilter As String ' Data type filter
    Dim path_trafo As String ' String being returned by the file dialog
    Dim trafoParams As trafo_Params ' Transformation parameters
    Dim newPlans As Variant ' The new plans to be georeferenced

    ' Create file dialog object
    Set fd = New FileDialogs
    
    strFilter = "Transformationen (*_trafo.txt)|*_trafo.txt" ' Only show files of transformation parameters
    fd.Filter = strFilter
    fd.Title = "Transformationssatz auswählen"
    
    ' Have the user pick the transformation file
    path_trafo = fd.ShowOpen
    
    ' Handle if nothing was selected
    If IsEmpty(path_trafo) Then
        MsgBox "Keine Dateien wurden ausgewählt.", vbOKOnly, "Ungültige Auswahl"
        End
    End If
    
    ' Load the set of parameters
    trafoParams = Read_Trafo_CSV(path_trafo)
    
    ' Select the new plans
    newPlans = Load_Additional_Files(path_trafo)
    
    ' Apply the transfromation parameters to the new plans
    Georef_Additional_Plans newPlans, trafoParams
    
End Sub

Attribute VB_Name = "ShellProcess"
Option Explicit

Private Type STARTUPINFO
cb As Long
lpReserved As String
lpDesktop As String
lpTitle As String
dwX As Long
dwY As Long
dwXSize As Long
dwYSize As Long
dwXCountChars As Long
dwYCountChars As Long
''' CREDIT: Microsoft Visual Basic Documentation

dwFillAttribute As Long
dwFlags As Long
wShowWindow As Integer
cbReserved2 As Integer
lpReserved2 As Long
hStdInput As Long
hStdOutput As Long
hStdError As Long
End Type

Private Type PROCESS_INFORMATION
hProcess As Long
hThread As Long
dwProcessID As Long
dwThreadID As Long
End Type

Private Declare PtrSafe Function WaitForSingleObject Lib "kernel32" (ByVal hHandle As Long, ByVal dwMilliseconds As Long) As Long

Private Declare PtrSafe Function CreateProcessA Lib "kernel32" (ByVal lpApplicationName As Long, ByVal lpCommandLine As String, ByVal lpProcessAttributes As Long, ByVal lpThreadAttributes As Long, ByVal bInheritHandles As Long, ByVal dwCreationFlags As Long, ByVal lpEnvironment As Long, ByVal lpCurrentDirectory As Long, lpStartupInfo As STARTUPINFO, lpProcessInformation As PROCESS_INFORMATION) As Long

Private Declare PtrSafe Function CloseHandle Lib "kernel32" (ByVal hObject As Long) As Long

Private Const NORMAL_PRIORITY_CLASS = &H20&
Private Const INFINITE = -1&

Public Sub ExecCmd(cmdline As String)
    Dim proc As PROCESS_INFORMATION
    Dim start As STARTUPINFO
    Dim ReturnValue As Integer
    
    ' Initialize the STARTUPINFO structure:
    start.cb = Len(start)
    
    ' Start the shelled application:
    ReturnValue = CreateProcessA(0&, cmdline$, 0&, 0&, 1&, _
    NORMAL_PRIORITY_CLASS, 0&, 0&, start, proc)
    
    ' Wait for the shelled application to finish:
    Do
    ReturnValue = WaitForSingleObject(proc.hProcess, 0)
    DoEvents
    Loop Until ReturnValue <> 258
    
    ReturnValue = CloseHandle(proc.hProcess)
End Sub

Attribute VB_Name = "frm_0_New_Old"
Attribute VB_Base = "0{73568CA5-2CA2-47BF-874F-7BF817CB22D3}{CC4FE70D-C109-4946-B731-22BC21C561BE}"
Attribute VB_GlobalNameSpace = False
Attribute VB_Creatable = False
Attribute VB_PredeclaredId = True
Attribute VB_Exposed = False
Attribute VB_TemplateDerived = False
Attribute VB_Customizable = False
Private Sub existingTrafo_Click()
    Me.Tag = 1
    frm_0_New_Old.Hide
End Sub

Private Sub newTrafo_Click()
    Me.Tag = 0
    frm_0_New_Old.Hide
End Sub

Attribute VB_Name = "frm_1_Georef"
Attribute VB_Base = "0{D739DD79-F4AB-45B1-BC51-D839C95E367B}{8AB536B1-199F-4ECB-A90B-21FA2C840AE4}"
Attribute VB_GlobalNameSpace = False
Attribute VB_Creatable = False
Attribute VB_PredeclaredId = True
Attribute VB_Exposed = False
Attribute VB_TemplateDerived = False
Attribute VB_Customizable = False
Option Explicit

Private Sub bt_Cancel_Click()
    Unload Me
End Sub

Private Sub bt_Laden_Click()
' Start der Anwendung

    Dim path_input As String
    Dim path_reference As String
    
    path_input = frm_1_Georef.txtb_Pfad_Fremddaten.Value
    path_reference = frm_1_Georef.txtb_Pfad_Referenzdaten.Value
    
    'Start
    frm_1_Georef.Hide
    Georef_Automation.Execute_Georef path_input, path_reference
    
    Load frm_2_AVCheck
    frm_2_AVCheck.Tag = path_input
    frm_2_AVCheck.show vbModeless
    
    
End Sub

Private Sub btn_browse_Fremd_Click()
'Pfad ermitteln Fremddatei

    Dim dwgNameFremddaten As String
    
    dwgNameFremddaten = OpenDialog(False) 'False = es handelt sich um die Fremddatendatei -> fuer Titelanzeige im Fenster
    frm_1_Georef.txtb_Pfad_Fremddaten.Value = dwgNameFremddaten
      
End Sub

Private Sub btn_browse_Fremd_georef_Click()
'Pfad/Speicherort des neuen georeferenzierten DWGs

    Dim dwgNameFremddaten_georef As String
    
    dwgNameFremddaten_georef = OpenDialog(False) 'False = es handelt sich um die Fremddatendatei -> fuer Titelanzeige im Fenster
    frm_1_Georef.txtb_Pfad_Fremddaten_georef.Value = dwgNameFremddaten_georef
    
End Sub

Private Sub btn_browse_Referenz_Click()
'Pfad ermitteln von Referenzdatei

    Dim dwgNameRef As String
     
    dwgNameRef = OpenDialog(True) 'True = es handelt sich um die Referenzdatei -> fuer Titelanzeige im Fenster
    frm_1_Georef.txtb_Pfad_Referenzdaten.Value = dwgNameRef
    
End Sub

Public Function OpenDialog(Refdatei As Boolean)
'Dialog fuer die Wahl der Datei

   Dim FileName As String
   'Using the SendCommand method, send getfiled AutoLISP expressions to the AutoCAD command line.
   'Set the return value to a user-defined system variable USERS1.
   If Refdatei = True Then
        ThisDrawing.SendCommand "(setvar " & """users1""" & "(getfiled " & """Wähle die Referenzdatei...""" & """p:/_Projekte/AutoCAD_Georef_VBA/""" & """dwg""" & "0)) "
   Else
        ThisDrawing.SendCommand "(setvar " & """users1""" & "(getfiled " & """Wähle die zu referenzierende Datei...""" & """p:/_Projekte/AutoCAD_Georef_VBA/""" & """dwg""" & "0)) "
   End If
   
   'Use the GetVariable method to retrieve this system variable to store the selected file name
   OpenDialog = ThisDrawing.GetVariable("users1")

End Function

Attribute VB_Name = "frm_2_AVCheck"
Attribute VB_Base = "0{19C1FA96-C5F0-4560-B117-A283B70A51CD}{21D4D415-71CF-4157-B2F9-5CF30926E61A}"
Attribute VB_GlobalNameSpace = False
Attribute VB_Creatable = False
Attribute VB_PredeclaredId = True
Attribute VB_Exposed = False
Attribute VB_TemplateDerived = False
Attribute VB_Customizable = False
Option Explicit

Private Sub bt_AVCheck_Click()

    frm_2_AVCheck.Hide
    
    ThisDrawing.Save
    
    Georef_Automation.Match_Plans (Me.Tag)
    'ThisDrawing.SendCommand "ADETRANSFORM" & vbCr
    
    
    'frm_3_Fremddaten_speichern.show vbModeless
    
    
End Sub

Private Sub bt_Cancel_Click()
    Unload Me
End Sub

Attribute VB_Name = "frm_3_1_Accept_Sims"
Attribute VB_Base = "0{18B5486C-037B-4C5E-8D6A-5EC6E7104341}{E451DF46-A0CA-4550-AB50-0831D5B11E52}"
Attribute VB_GlobalNameSpace = False
Attribute VB_Creatable = False
Attribute VB_PredeclaredId = True
Attribute VB_Exposed = False
Attribute VB_TemplateDerived = False
Attribute VB_Customizable = False
Private Sub Accept_Click()
    Me.Tag = -1
    frm_3_1_Accept_Sims.Hide
End Sub

Private Sub Rep_Both_Click()
    Me.Tag = 0
    frm_3_1_Accept_Sims.Hide
End Sub

Private Sub Rep_Ref_Click()
    Me.Tag = 2
    frm_3_1_Accept_Sims.Hide
End Sub

Attribute VB_Name = "frm_3_Stop_Execution"
Attribute VB_Base = "0{73F9D42E-19DF-40F7-A813-07035026CBDA}{E7087A60-23B4-4576-8896-C4B8EF3211A1}"
Attribute VB_GlobalNameSpace = False
Attribute VB_Creatable = False
Attribute VB_PredeclaredId = True
Attribute VB_Exposed = False
Attribute VB_TemplateDerived = False
Attribute VB_Customizable = False
Private Sub repeat_selection_all_Click()
    Me.Tag = 0
    frm_3_Stop_Execution.Hide
End Sub

Private Sub repeat_selection_current_Click()
    frm_3_Stop_Execution.Hide
End Sub

Private Sub stop_execution_Click()
    End
End Sub

Attribute VB_Name = "frm_4_Scale"
Attribute VB_Base = "0{286C81CC-14C3-4D42-A8D3-D2535F7FAFF3}{ED4A93BD-7749-462D-BC6C-8666A0E14F99}"
Attribute VB_GlobalNameSpace = False
Attribute VB_Creatable = False
Attribute VB_PredeclaredId = True
Attribute VB_Exposed = False
Attribute VB_TemplateDerived = False
Attribute VB_Customizable = False
Public known_scale As Double

Private Sub button_scale_known_Click()
    If frm_4_Scale.known_scale_checkbox.Value = True Then
        known_scale = known_scale_value.Value
    Else
        known_scale = -1
    End If
    
    frm_4_Scale.Hide
End Sub

Private Sub cancel_Click()
    Unload Me
    End
End Sub

Private Sub known_scale_checkbox_Click()
    If frm_4_Scale.known_scale_checkbox.Value = True Then
        frm_4_Scale.known_scale_value.Enabled = True
    Else
        frm_4_Scale.known_scale_value.Enabled = False
    End If
End Sub

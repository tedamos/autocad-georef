Attribute VB_Name = "Georef_VBA"
Option Explicit
Sub Main_Georef_VBA()

    '1. Formular anzeigen
    frm_1_Georef.show vbModeless

End Sub

Sub Georef_VBA_start(Pfad_Fremddatei As String, Pfad_Referenzdatei As String)

    Dim Pfad_Fremddatei_georef As String
    
    Dim BoundingBox_Fremddaten As Variant
    Dim BoundingBox_Referenzdaten As Variant

    
    'neue Zeichnung erstellen mit Name der Fremdatendatei + _georef
    '-------------------------
    
    'Name neuer DWG Datei
    Pfad_Fremddatei_georef = Left(Pfad_Fremddatei, (Len(Pfad_Fremddatei) - 4)) & "_georef.dwg"
    
    'Neue Zeichnung erstellen
    StartNewAutoCADfile (Pfad_Fremddatei_georef)
    
    
    'Zeichnungen referenzieren, zwei Fenster erstellen in Datei und auf Bereiche Zoomen
    '-------------------------------------------------------
    BoundingBox_Fremddaten = AttachingExternalReference(Pfad_Fremddatei)
    BoundingBox_Referenzdaten = AttachingExternalReference(Pfad_Referenzdatei)
    
    Split_View BoundingBox_Fremddaten, BoundingBox_Referenzdaten

    

End Sub

Sub Split_View(BBox_Fremd As Variant, BBox_Referenz As Variant)

  Dim vportFremdd As AcadViewport
  Dim vportReferenzd As AcadViewport
  
  Dim point1(0 To 2) As Double
  Dim point1_2D(0 To 1) As Double
  
  Dim point2(0 To 2) As Double
  Dim point2_2D(0 To 1) As Double
  
    
  ThisDrawing.ActiveSpace = acModelSpace

  'Viewports erstellen
   Set vportFremdd = ThisDrawing.ActiveViewport
   
   point1(0) = BBox_Fremd(0): point1(1) = BBox_Fremd(1): point1(2) = 0
   point2(0) = BBox_Fremd(3): point2(1) = BBox_Fremd(4): point2(2) = 0
   point1_2D(0) = ((BBox_Fremd(0) + BBox_Fremd(3)) / 2): point1_2D(1) = ((BBox_Fremd(1) + BBox_Fremd(4)) / 2)
   
   vportFremdd.Center = point1_2D
   vportFremdd.Width = Abs(BBox_Fremd(0) - BBox_Fremd(3))
   vportFremdd.Height = Abs(BBox_Fremd(1) - BBox_Fremd(4))

   ThisDrawing.ActiveViewport = vportFremdd
   ZoomWindow point1, point2
   
   
   'Viewports vertikal trennen
   vportFremdd.Split acViewport2Vertical

    point1(0) = BBox_Referenz(0): point1(1) = BBox_Referenz(1): point1(2) = 0
    point2(0) = BBox_Referenz(3): point2(1) = BBox_Referenz(4): point2(2) = 0
    point1_2D(0) = ((BBox_Referenz(0) + BBox_Referenz(3)) / 2): point1_2D(1) = ((BBox_Referenz(1) + BBox_Referenz(4)) / 2)
    
    vportFremdd.Center = point1_2D
    vportFremdd.Width = Abs(BBox_Fremd(0) - BBox_Fremd(3))
    vportFremdd.Height = Abs(BBox_Fremd(1) - BBox_Fremd(4))

    ThisDrawing.ActiveViewport = vportFremdd
    ZoomWindow point1, point2
   
End Sub


Public Function StartNewAutoCADfile(strFileName As String) As AcadDocument

     Dim objAcadDoc As AcadDocument
     Dim AcadApp As AcadApplication
    
     Set AcadApp = ThisDrawing.Application
    
     If Len(strFileName) > 0 Then
        Set objAcadDoc = AcadApp.Documents.Add
        objAcadDoc.SaveAs (strFileName)
        Set StartNewAutoCADfile = objAcadDoc
     Else
        StartNewAutoCADfile = Nothing
     End If

 End Function

Function AttachingExternalReference(PathName As String) As Variant

     Dim BoundBox As Variant
     Dim utilObj As Object
     
     Dim InsertPoint(0 To 2) As Double
     Dim insertedBlock As AcadExternalReference
     Dim tempBlock As AcadBlock
     Dim tempBlockRef As AcadBlockReference
     Dim msg As String
     Dim Ref_Name As String
     Dim explodedObj As Variant
          
     Dim minExt As Variant
     Dim maxExt As Variant
          
     'Definition von Punkten für die Referenzierung
     InsertPoint(0) = 1
     InsertPoint(1) = 1
     InsertPoint(2) = 0
     

      Ref_Name = Split(PathName, "\")(UBound(Split(PathName, "\")))
     
     'Referenz zur Zeichnung hinzufügen
      Set insertedBlock = ThisDrawing.ModelSpace.AttachExternalReference(PathName, Ref_Name, InsertPoint, 1, 1, 1, 0, False)
      insertedBlock.Update
      
      insertedBlock.GetBoundingBox minExt, maxExt
     
      'Set tempBlockRef = ThisDrawing.ModelSpace.InsertBlock(InsertPoint, Ref_Name, 1, 1, 1, 0)
      'tempBlockRef.Explode
      'tempBlockRef.GetBoundingBox minExt, maxExt
      
      'Set tempBlock = ThisDrawing.Blocks.ObjectName(tempBlockRef.Name)
      'tempBlockRef.Delete
      'tempBlock.Delete
      
      '  For Each tempBlock In ThisDrawing.Blocks
      '        If tempBlock.IsXRef Then
      '            'Set tempBlockRef = tempBlock
      '            If (InStr(1, tempBlock.Name, Left(Ref_Name, Len(Ref_Name) - 4), vbTextCompare)) Then
      '                 tempBlock.Explode
      '                 tempBlock.Bind (False)
      '
      '                Exit For
      '            End If
      '         End If
      '    Next
     
     
     'Set tempBlock = ThisDrawing.ModelSpace.InsertBlock(InsertPoint, PathName, 1, 1, 1, 0)
     'tempBlock.Explode
     
     'tempBlock.GetBoundingBox minExt, maxExt
     
     
     
     Set utilObj = ThisDrawing.Utility
     utilObj.CreateTypedArray BoundBox, vbDouble, minExt(0), minExt(1), minExt(2), maxExt(0), maxExt(1), maxExt(2)
     
     AttachingExternalReference = BoundBox

End Function

Sub DetachingExternalReference(PathName As String)
    
    Dim Ref_Name As String

    Ref_Name = Split(PathName, "\")(UBound(Split(PathName, "\")))

    ThisDrawing.Blocks.Item(Ref_Name).Detach
    

End Sub

Sub CopyXrefSubent2ThisDwg(Fremddaten_Name As String)

    Dim Object As Object
    Dim subObject As Object
    
    Dim retObjects As Variant
    Dim PickedPoint As Variant
    Dim TransMatrix As Variant
    Dim ContextData As Variant
    
    Dim bIsXRef As Boolean
    Dim i As Integer
    
    ' Create the selection set
    'Dim ssetObj As AcadSelectionSet
    'Set ssetObj = ThisDrawing.SelectionSets.Add("SSET")
    
    'ssetObj.Select acSelectionSetAll
    
    
    ThisDrawing.Utility.GetSubEntity subObject, PickedPoint, TransMatrix, ContextData
    If Not (VarType(ContextData) = vbEmpty) Then
        For i = LBound(ContextData) To UBound(ContextData)
            Set Object = ThisDrawing.ObjectIdToObject(ContextData(i))
            'If Object.ObjectName = "AcDbBlockReference" Then
            If ThisDrawing.Blocks.Item(Fremddaten_Name).IsXRef = True Then
                    bIsXRef = True
                    Exit For
            Else
                    bIsXRef = False
            End If
            'Else
                    bIsXRef = False
           ' End If
        Next
        
        If bIsXRef = True Then
            Dim owner As AcadBlock, blk As AcadBlock
            Dim obj As Object
            Dim objects() As Object
            Dim xrefDB As AcadDatabase
    
            Set xrefDB = ThisDrawing.Blocks.Item(Fremddaten_Name).XRefDatabase
            ' add each entity in the Xref database to the objects array
            Set blk = xrefDB.ModelSpace
            i = 0
            
            For Each obj In blk
                If obj.ObjectID = subObject.ObjectID Then
                    ReDim Preserve objects(i)
                    Set objects(i) = obj
                    i = i + 1
                End If
            Next obj
            ' copying the object in the current drawing model space
            Set owner = ThisDrawing.ModelSpace
            retObjects = xrefDB.CopyObjects(objects, owner)


            ' change copied object's layer to same as the blockref
           For i = 0 To UBound(retObjects)
                retObjects(i).Layer = Object.Layer
            Next


        Else
            MsgBox "Object selected is not an XRef"
        End If
    Else
        MsgBox "Object selected is not an AcDbBlockReference"
    End If
End Sub

Attribute VB_Name = "frm_1_Georef"
Attribute VB_Base = "0{4F91AF13-FCB8-47C4-BEFC-F17BB28D0C48}{9B5EA46B-D28D-45E8-A714-1A6F606BDD27}"
Attribute VB_GlobalNameSpace = False
Attribute VB_Creatable = False
Attribute VB_PredeclaredId = True
Attribute VB_Exposed = False
Attribute VB_TemplateDerived = False
Attribute VB_Customizable = False
Option Explicit

Private Sub bt_Cancel_Click()
    Unload Me
End Sub

Private Sub bt_Laden_Click()
' Start der Anwendung

    Dim path_Referenz As String
    Dim path_Fremddatei As String
    
    path_Fremddatei = frm_1_Georef.txtb_Pfad_Fremddaten.Value
    path_Referenz = frm_1_Georef.txtb_Pfad_Referenzdaten.Value

    'Start
    frm_1_Georef.Hide
    Georef_VBA.Georef_VBA_start path_Fremddatei, path_Referenz
    
    frm_2_AVCheck.show vbModeless
    
    
End Sub

Private Sub btn_browse_Fremd_Click()
'Pfad ermitteln Fremddatei

    Dim dwgNameFremddaten As String
    
    dwgNameFremddaten = OpenDialog(False) 'False = es handelt sich um die Fremddatendatei -> fuer Titelanzeige im Fenster
    frm_1_Georef.txtb_Pfad_Fremddaten.Value = dwgNameFremddaten
      
End Sub

Private Sub btn_browse_Fremd_georef_Click()
'Pfad/Speicherort des neuen georeferenzierten DWGs

    Dim dwgNameFremddaten_georef As String
    
    dwgNameFremddaten_georef = OpenDialog(False) 'False = es handelt sich um die Fremddatendatei -> fuer Titelanzeige im Fenster
    frm_1_Georef.txtb_Pfad_Fremddaten_georef.Value = dwgNameFremddaten_georef
    
End Sub

Private Sub btn_browse_Referenz_Click()
'Pfad ermitteln von Referenzdatei

    Dim dwgNameRef As String
     
    dwgNameRef = OpenDialog(True) 'True = es handelt sich um die Referenzdatei -> fuer Titelanzeige im Fenster
    frm_1_Georef.txtb_Pfad_Referenzdaten.Value = dwgNameRef
    
End Sub

Public Function OpenDialog(Refdatei As Boolean)
'Dialog fuer die Wahl der Datei

   Dim fileName As String
   'Using the SendCommand method, send getfiled AutoLISP expressions to the AutoCAD command line.
   'Set the return value to a user-defined system variable USERS1.
   If Refdatei = True Then
        ThisDrawing.SendCommand "(setvar " & """users1""" & "(getfiled " & """Wähle die Referenzdatei...""" & """p:/_Projekte/AutoCAD_Georef_VBA/""" & """dwg""" & "8)) "
   Else
        ThisDrawing.SendCommand "(setvar " & """users1""" & "(getfiled " & """Wähle die zu referenzierende Datei...""" & """p:/_Projekte/AutoCAD_Georef_VBA/""" & """dwg""" & "8)) "
   End If
   
   'Use the GetVariable method to retrieve this system variable to store the selected file name
   OpenDialog = ThisDrawing.GetVariable("users1")

End Function

Attribute VB_Name = "frm_2_AVCheck"
Attribute VB_Base = "0{073CC0DE-22A8-4D29-9C6D-A9ABB39097C2}{48353FD2-E89A-46F1-A0A7-F33EB950E637}"
Attribute VB_GlobalNameSpace = False
Attribute VB_Creatable = False
Attribute VB_PredeclaredId = True
Attribute VB_Exposed = False
Attribute VB_TemplateDerived = False
Attribute VB_Customizable = False
Option Explicit


Private Sub bt_AVCheck_Click()

    frm_2_AVCheck.Hide
    
    ThisDrawing.Save
    ThisDrawing.SendCommand "ADETRANSFORM" & vbCr
    
    
    frm_3_Fremddaten_speichern.show vbModeless
    
    
End Sub

Private Sub bt_Cancel_Click()
    Unload Me
End Sub

Attribute VB_Name = "frm_3_Fremddaten_speichern"
Attribute VB_Base = "0{E83D2A6B-FA2E-465F-9699-1A281304C6B0}{329C17B9-AAB8-4BAF-B12E-684FEE5AED33}"
Attribute VB_GlobalNameSpace = False
Attribute VB_Creatable = False
Attribute VB_PredeclaredId = True
Attribute VB_Exposed = False
Attribute VB_TemplateDerived = False
Attribute VB_Customizable = False
Option Explicit

Private Sub bt_Cancel_Click()
    Unload Me
End Sub

Private Sub bt_fertigstellen_Click()
    
    Dim path_Referenz As String
    Dim path_Fremddatei As String
    Dim Name_Fremddaten As String
    
    path_Fremddatei = frm_1_Georef.txtb_Pfad_Fremddaten.Value
    path_Referenz = frm_1_Georef.txtb_Pfad_Referenzdaten.Value

    If frm_3_Fremddaten_speichern.chkb_Fremd_Kopieren = True Then
        'Daten in Datei Fremddaten wählen und in aktuelle Zeichnung kopieren
         Name_Fremddaten = Split(path_Fremddatei, "\")(UBound(Split(path_Fremddatei, "\")))
         CopyXrefSubent2ThisDwg Name_Fremddaten
    End If
    
    If frm_3_Fremddaten_speichern.Ckb_Fremd_abhaengen = True Then
        'Fremddaten abhängen
        'Georef_VBA.DetachingExternalReference path_Fremddatei
    End If
    
    If frm_3_Fremddaten_speichern.Ckb_Referenz_abhaengen = True Then
        'Referenzdaten abhängen
        'Georef_VBA.DetachingExternalReference path_Referenz
    End If
    
    'Zeichnung speichern
    ThisDrawing.Save
    
    
End Sub
